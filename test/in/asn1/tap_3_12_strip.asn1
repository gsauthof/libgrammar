DataInterChange ::= CHOICE
{
  transferBatch TransferBatch,
  notification Notification,
  ...
}

TransferBatch ::= [APPLICATION 1] SEQUENCE
{
  batchControlInfo BatchControlInfo,
  accountingInfo AccountingInfo OPTIONAL,
  networkInfo NetworkInfo,
  messageDescriptionInfo MessageDescriptionInfoList OPTIONAL,
  callEventDetails CallEventDetailList,
  auditControlInfo AuditControlInfo,
  ...
}

Notification ::= [APPLICATION 2] SEQUENCE
{
  sender Sender,
  recipient Recipient,
  fileSequenceNumber FileSequenceNumber,
  rapFileSequenceNumber RapFileSequenceNumber OPTIONAL,
  fileCreationTimeStamp FileCreationTimeStamp OPTIONAL,
  fileAvailableTimeStamp FileAvailableTimeStamp,
  transferCutOffTimeStamp TransferCutOffTimeStamp,
  specificationVersionNumber SpecificationVersionNumber,
  releaseVersionNumber ReleaseVersionNumber,
  fileTypeIndicator FileTypeIndicator OPTIONAL,
  operatorSpecInformation OperatorSpecInfoList OPTIONAL,
  ...
}

CallEventDetailList ::= [APPLICATION 3] SEQUENCE OF CallEventDetail

CallEventDetail ::= CHOICE
{
  mobileOriginatedCall MobileOriginatedCall,
  mobileTerminatedCall MobileTerminatedCall,
  supplServiceEvent SupplServiceEvent,
  serviceCentreUsage ServiceCentreUsage,
  gprsCall GprsCall,
  contentTransaction ContentTransaction,
  locationService LocationService,
  messagingEvent MessagingEvent,
  mobileSession MobileSession,
  ...
}

BatchControlInfo ::= [APPLICATION 4] SEQUENCE
{
  sender Sender,
  recipient Recipient,
  fileSequenceNumber FileSequenceNumber,
  fileCreationTimeStamp FileCreationTimeStamp OPTIONAL,
  transferCutOffTimeStamp TransferCutOffTimeStamp,
  fileAvailableTimeStamp FileAvailableTimeStamp,
  specificationVersionNumber SpecificationVersionNumber,
  releaseVersionNumber ReleaseVersionNumber,
  fileTypeIndicator FileTypeIndicator OPTIONAL,
  rapFileSequenceNumber RapFileSequenceNumber OPTIONAL,
  operatorSpecInformation OperatorSpecInfoList OPTIONAL,
  ...
}

AccountingInfo ::= [APPLICATION 5] SEQUENCE
{
  taxation TaxationList OPTIONAL,
  discounting DiscountingList OPTIONAL,
  localCurrency LocalCurrency,
  tapCurrency TapCurrency OPTIONAL,
  currencyConversionInfo CurrencyConversionList OPTIONAL,
  tapDecimalPlaces TapDecimalPlaces,
  ...
}

NetworkInfo ::= [APPLICATION 6] SEQUENCE
{
  utcTimeOffsetInfo UtcTimeOffsetInfoList,
  recEntityInfo RecEntityInfoList OPTIONAL,
  ...
}

MessageDescriptionInfoList ::= [APPLICATION 8] SEQUENCE OF MessageDescriptionInformation

MobileOriginatedCall ::= [APPLICATION 9] SEQUENCE
{
  basicCallInformation MoBasicCallInformation,
  locationInformation LocationInformation,
  equipmentIdentifier ImeiOrEsn OPTIONAL,
  basicServiceUsedList BasicServiceUsedList,
  supplServiceCode SupplServiceCode OPTIONAL,
  thirdPartyInformation ThirdPartyInformation OPTIONAL,
  camelServiceUsed CamelServiceUsed OPTIONAL,
  operatorSpecInformation OperatorSpecInfoList OPTIONAL,
  ...
}

MobileTerminatedCall ::= [APPLICATION 10] SEQUENCE
{
  basicCallInformation MtBasicCallInformation,
  locationInformation LocationInformation,
  equipmentIdentifier ImeiOrEsn OPTIONAL,
  basicServiceUsedList BasicServiceUsedList,
  camelServiceUsed CamelServiceUsed OPTIONAL,
  operatorSpecInformation OperatorSpecInfoList OPTIONAL,
  ...
}

SupplServiceEvent ::= [APPLICATION 11] SEQUENCE
{
  chargeableSubscriber ChargeableSubscriber,
  rapFileSequenceNumber RapFileSequenceNumber OPTIONAL,
  locationInformation LocationInformation,
  equipmentIdentifier ImeiOrEsn OPTIONAL,
  supplServiceUsed SupplServiceUsed,
  operatorSpecInformation OperatorSpecInfoList OPTIONAL,
  ...
}

ServiceCentreUsage ::= [APPLICATION 12] SEQUENCE
{
  basicInformation ScuBasicInformation,
  rapFileSequenceNumber RapFileSequenceNumber OPTIONAL,
  servingNetwork ServingNetwork OPTIONAL,
  recEntityCode RecEntityCode,
  chargeInformation ChargeInformation,
  scuChargeType ScuChargeType,
  scuTimeStamps ScuTimeStamps,
  operatorSpecInformation OperatorSpecInfoList OPTIONAL,
  ...
}

GprsCall ::= [APPLICATION 14] SEQUENCE
{
  gprsBasicCallInformation GprsBasicCallInformation,
  gprsLocationInformation GprsLocationInformation,
  equipmentIdentifier ImeiOrEsn OPTIONAL,
  gprsServiceUsed GprsServiceUsed,
  camelServiceUsed CamelServiceUsed OPTIONAL,
  operatorSpecInformation OperatorSpecInfoList OPTIONAL,
  ...
}

ContentTransaction ::= [APPLICATION 17] SEQUENCE
{
  contentTransactionBasicInfo ContentTransactionBasicInfo,
  chargedPartyInformation ChargedPartyInformation,
  servingPartiesInformation ServingPartiesInformation,
  contentServiceUsed ContentServiceUsedList,
  operatorSpecInformation OperatorSpecInfoList OPTIONAL,
  ...
}

LocationService ::= [APPLICATION 297] SEQUENCE
{
  rapFileSequenceNumber RapFileSequenceNumber OPTIONAL,
  recEntityCode RecEntityCode,
  callReference CallReference OPTIONAL,
  trackingCustomerInformation TrackingCustomerInformation OPTIONAL,
  lCSSPInformation LCSSPInformation OPTIONAL,
  trackedCustomerInformation TrackedCustomerInformation OPTIONAL,
  locationServiceUsage LocationServiceUsage,
  operatorSpecInformation OperatorSpecInfoList OPTIONAL,
  ...
}

MessagingEvent ::= [APPLICATION 433] SEQUENCE
{
  messagingEventService MessagingEventService,
  chargedParty ChargedParty,
  rapFileSequenceNumber RapFileSequenceNumber OPTIONAL,
  simToolkitIndicator SimToolkitIndicator OPTIONAL,
  geographicalLocation GeographicalLocation OPTIONAL,
  eventReference EventReference,
  recEntityCodeList RecEntityCodeList,
  networkElementList NetworkElementList OPTIONAL,
  locationArea LocationArea OPTIONAL,
  cellId CellId OPTIONAL,
  serviceStartTimestamp ServiceStartTimestamp,
  nonChargedParty NonChargedParty OPTIONAL,
  exchangeRateCode ExchangeRateCode OPTIONAL,
  callTypeGroup CallTypeGroup,
  charge Charge,
  taxInformationList TaxInformationList OPTIONAL,
  operatorSpecInformation OperatorSpecInfoList OPTIONAL,
  ...
}

MobileSession ::= [APPLICATION 434] SEQUENCE
{
  mobileSessionService MobileSessionService,
  chargedParty ChargedParty,
  rapFileSequenceNumber RapFileSequenceNumber OPTIONAL,
  simToolkitIndicator SimToolkitIndicator OPTIONAL,
  geographicalLocation GeographicalLocation OPTIONAL,
  locationArea LocationArea OPTIONAL,
  cellId CellId OPTIONAL,
  eventReference EventReference,
  recEntityCodeList RecEntityCodeList,
  serviceStartTimestamp ServiceStartTimestamp,
  causeForTerm CauseForTerm OPTIONAL,
  totalCallEventDuration TotalCallEventDuration,
  nonChargedParty NonChargedParty OPTIONAL,
  requestedDestination RequestedDestination OPTIONAL,
  sessionChargeInfoList SessionChargeInfoList,
  operatorSpecInformation OperatorSpecInfoList OPTIONAL,
  ...
}

AuditControlInfo ::= [APPLICATION 15] SEQUENCE
{
  earliestCallTimeStamp EarliestCallTimeStamp OPTIONAL,
  latestCallTimeStamp LatestCallTimeStamp OPTIONAL,
  totalCharge TotalCharge,
  totalChargeRefund TotalChargeRefund OPTIONAL,
  totalTaxRefund TotalTaxRefund OPTIONAL,
  totalTaxValue TotalTaxValue,
  totalDiscountValue TotalDiscountValue,
  totalDiscountRefund TotalDiscountRefund OPTIONAL,
  totalAdvisedChargeValueList TotalAdvisedChargeValueList OPTIONAL,
  callEventDetailsCount CallEventDetailsCount,
  operatorSpecInformation OperatorSpecInfoList OPTIONAL,
  ...
}

AccessPointNameNI ::= [APPLICATION 261] AsciiString (SIZE(1..63))

AccessPointNameOI ::= [APPLICATION 262] AsciiString (SIZE(1..37))

ActualDeliveryTimeStamp ::= [APPLICATION 302] DateTime

AddressStringDigits ::= BCDString

AdvisedCharge ::= [APPLICATION 349] Charge

AdvisedChargeCurrency ::= [APPLICATION 348] Currency

AdvisedChargeInformation ::= [APPLICATION 351] SEQUENCE
{
  paidIndicator PaidIndicator OPTIONAL,
  paymentMethod PaymentMethod OPTIONAL,
  advisedChargeCurrency AdvisedChargeCurrency OPTIONAL,
  advisedCharge AdvisedCharge,
  commission Commission OPTIONAL,
  ...
}

AgeOfLocation ::= [APPLICATION 396] INTEGER

BasicService ::= [APPLICATION 36] SEQUENCE
{
  serviceCode BasicServiceCode,
  transparencyIndicator TransparencyIndicator OPTIONAL,
  fnur Fnur OPTIONAL,
  userProtocolIndicator UserProtocolIndicator OPTIONAL,
  guaranteedBitRate GuaranteedBitRate OPTIONAL,
  maximumBitRate MaximumBitRate OPTIONAL,
  ...
}

BasicServiceCode ::= [APPLICATION 426] CHOICE
{
  teleServiceCode TeleServiceCode,
  bearerServiceCode BearerServiceCode,
  ...
}

BasicServiceCodeList ::= [APPLICATION 37] SEQUENCE OF BasicServiceCode

BasicServiceUsed ::= [APPLICATION 39] SEQUENCE
{
  basicService BasicService,
  chargingTimeStamp ChargingTimeStamp OPTIONAL,
  chargeInformationList ChargeInformationList,
  hSCSDIndicator HSCSDIndicator OPTIONAL,
  ...
}

BasicServiceUsedList ::= [APPLICATION 38] SEQUENCE OF BasicServiceUsed

BearerServiceCode ::= [APPLICATION 40] HexString (SIZE(2))

CalledNumber ::= [APPLICATION 407] AddressStringDigits

CalledPlace ::= [APPLICATION 42] AsciiString

CalledRegion ::= [APPLICATION 46] AsciiString

CallEventDetailsCount ::= [APPLICATION 43] INTEGER

CallEventStartTimeStamp ::= [APPLICATION 44] DateTime

CallingNumber ::= [APPLICATION 405] AddressStringDigits

CallOriginator ::= [APPLICATION 41] SEQUENCE
{
  callingNumber CallingNumber OPTIONAL,
  clirIndicator ClirIndicator OPTIONAL,
  sMSOriginator SMSOriginator OPTIONAL,
  ...
}

CallReference ::= [APPLICATION 45] OCTET STRING (SIZE(1..8))

CallTypeGroup ::= [APPLICATION 258] SEQUENCE
{
  callTypeLevel1 CallTypeLevel1,
  callTypeLevel2 CallTypeLevel2,
  callTypeLevel3 CallTypeLevel3,
  ...
}

CallTypeLevel1 ::= [APPLICATION 259] INTEGER

CallTypeLevel2 ::= [APPLICATION 255] INTEGER

CallTypeLevel3 ::= [APPLICATION 256] INTEGER

CamelDestinationNumber ::= [APPLICATION 404] AddressStringDigits

CamelInvocationFee ::= [APPLICATION 422] AbsoluteAmount

CamelServiceKey ::= [APPLICATION 55] INTEGER

CamelServiceLevel ::= [APPLICATION 56] INTEGER

CamelServiceUsed ::= [APPLICATION 57] SEQUENCE
{
  camelServiceLevel CamelServiceLevel OPTIONAL,
  camelServiceKey CamelServiceKey,
  defaultCallHandling DefaultCallHandlingIndicator OPTIONAL,
  exchangeRateCode ExchangeRateCode OPTIONAL,
  taxInformation TaxInformationList OPTIONAL,
  discountInformation DiscountInformation OPTIONAL,
  camelInvocationFee CamelInvocationFee OPTIONAL,
  threeGcamelDestination ThreeGcamelDestination OPTIONAL,
  cseInformation CseInformation OPTIONAL,
  ...
}

CauseForTerm ::= [APPLICATION 58] INTEGER

CellId ::= [APPLICATION 59] INTEGER

Charge ::= [APPLICATION 62] AbsoluteAmount

ChargeableSubscriber ::= [APPLICATION 427] CHOICE
{
  simChargeableSubscriber SimChargeableSubscriber,
  minChargeableSubscriber MinChargeableSubscriber,
  ...
}

ChargeableUnits ::= [APPLICATION 65] INTEGER

ChargeDetail ::= [APPLICATION 63] SEQUENCE
{
  chargeType ChargeType,
  charge Charge,
  chargeableUnits ChargeableUnits OPTIONAL,
  chargedUnits ChargedUnits OPTIONAL,
  chargeDetailTimeStamp ChargeDetailTimeStamp OPTIONAL,
  ...
}

ChargeDetailList ::= [APPLICATION 64] SEQUENCE OF ChargeDetail

ChargeDetailTimeStamp ::= [APPLICATION 410] ChargingTimeStamp

ChargedItem ::= [APPLICATION 66] AsciiString (SIZE(1))

ChargedParty ::= [APPLICATION 436] SEQUENCE
{
  imsi Imsi,
  msisdn Msisdn OPTIONAL,
  publicUserId PublicUserId OPTIONAL,
  homeBid HomeBid OPTIONAL,
  homeLocationDescription HomeLocationDescription OPTIONAL,
  imei Imei OPTIONAL,
  ...
}

ChargedPartyEquipment ::= [APPLICATION 323] SEQUENCE
{
  equipmentIdType EquipmentIdType,
  equipmentId EquipmentId,
  ...
}

ChargedPartyHomeIdentification ::= [APPLICATION 313] SEQUENCE
{
  homeIdType HomeIdType,
  homeIdentifier HomeIdentifier,
  ...
}

ChargedPartyHomeIdList ::= [APPLICATION 314] SEQUENCE OF ChargedPartyHomeIdentification

ChargedPartyIdentification ::= [APPLICATION 309] SEQUENCE
{
  chargedPartyIdType ChargedPartyIdType,
  chargedPartyIdentifier ChargedPartyIdentifier,
  ...
}

ChargedPartyIdentifier ::= [APPLICATION 287] AsciiString

ChargedPartyIdList ::= [APPLICATION 310] SEQUENCE OF ChargedPartyIdentification

ChargedPartyIdType ::= [APPLICATION 305] INTEGER

ChargedPartyInformation ::= [APPLICATION 324] SEQUENCE
{
  chargedPartyIdList ChargedPartyIdList,
  chargedPartyHomeIdList ChargedPartyHomeIdList OPTIONAL,
  chargedPartyLocationList ChargedPartyLocationList OPTIONAL,
  chargedPartyEquipment ChargedPartyEquipment OPTIONAL,
  ...
}

ChargedPartyLocation ::= [APPLICATION 320] SEQUENCE
{
  locationIdType LocationIdType,
  locationIdentifier LocationIdentifier,
  ...
}

ChargedPartyLocationList ::= [APPLICATION 321] SEQUENCE OF ChargedPartyLocation

ChargedPartyStatus ::= [APPLICATION 67] INTEGER

ChargedUnits ::= [APPLICATION 68] INTEGER

ChargeInformation ::= [APPLICATION 69] SEQUENCE
{
  chargedItem ChargedItem,
  exchangeRateCode ExchangeRateCode OPTIONAL,
  callTypeGroup CallTypeGroup OPTIONAL,
  chargeDetailList ChargeDetailList,
  taxInformation TaxInformationList OPTIONAL,
  discountInformation DiscountInformation OPTIONAL,
  ...
}

ChargeInformationList ::= [APPLICATION 70] SEQUENCE OF ChargeInformation

ChargeRefundIndicator ::= [APPLICATION 344] INTEGER

ChargeType ::= [APPLICATION 71] NumberString (SIZE(2..3))

ChargingId ::= [APPLICATION 72] INTEGER

ChargingPoint ::= [APPLICATION 73] AsciiString (SIZE(1))

ChargingTimeStamp ::= [APPLICATION 74] DateTime

ClirIndicator ::= [APPLICATION 75] INTEGER

Commission ::= [APPLICATION 350] Charge

CompletionTimeStamp ::= [APPLICATION 76] DateTime

ContentChargingPoint ::= [APPLICATION 345] INTEGER

ContentProvider ::= [APPLICATION 327] SEQUENCE
{
  contentProviderIdType ContentProviderIdType,
  contentProviderIdentifier ContentProviderIdentifier,
  ...
}

ContentProviderIdentifier ::= [APPLICATION 292] AsciiString

ContentProviderIdList ::= [APPLICATION 328] SEQUENCE OF ContentProvider

ContentProviderIdType ::= [APPLICATION 291] INTEGER

ContentProviderName ::= [APPLICATION 334] AsciiString

ContentServiceUsed ::= [APPLICATION 352] SEQUENCE
{
  contentTransactionCode ContentTransactionCode,
  contentTransactionType ContentTransactionType,
  objectType ObjectType OPTIONAL,
  transactionDescriptionSupp TransactionDescriptionSupp OPTIONAL,
  transactionShortDescription TransactionShortDescription,
  transactionDetailDescription TransactionDetailDescription OPTIONAL,
  transactionIdentifier TransactionIdentifier,
  transactionAuthCode TransactionAuthCode OPTIONAL,
  dataVolumeIncoming DataVolumeIncoming OPTIONAL,
  dataVolumeOutgoing DataVolumeOutgoing OPTIONAL,
  totalDataVolume TotalDataVolume OPTIONAL,
  chargeRefundIndicator ChargeRefundIndicator OPTIONAL,
  contentChargingPoint ContentChargingPoint OPTIONAL,
  chargeInformationList ChargeInformationList OPTIONAL,
  advisedChargeInformation AdvisedChargeInformation OPTIONAL,
  ...
}

ContentServiceUsedList ::= [APPLICATION 285] SEQUENCE OF ContentServiceUsed

ContentTransactionBasicInfo ::= [APPLICATION 304] SEQUENCE
{
  rapFileSequenceNumber RapFileSequenceNumber OPTIONAL,
  orderPlacedTimeStamp OrderPlacedTimeStamp OPTIONAL,
  requestedDeliveryTimeStamp RequestedDeliveryTimeStamp OPTIONAL,
  actualDeliveryTimeStamp ActualDeliveryTimeStamp OPTIONAL,
  totalTransactionDuration TotalTransactionDuration OPTIONAL,
  transactionStatus TransactionStatus OPTIONAL,
  ...
}

ContentTransactionCode ::= [APPLICATION 336] INTEGER

ContentTransactionType ::= [APPLICATION 337] INTEGER

CseInformation ::= [APPLICATION 79] OCTET STRING (SIZE(1..40))

CurrencyConversion ::= [APPLICATION 106] SEQUENCE
{
  exchangeRateCode ExchangeRateCode,
  numberOfDecimalPlaces NumberOfDecimalPlaces,
  exchangeRate ExchangeRate,
  ...
}

CurrencyConversionList ::= [APPLICATION 80] SEQUENCE OF CurrencyConversion

CustomerIdentifier ::= [APPLICATION 364] AsciiString

CustomerIdType ::= [APPLICATION 363] INTEGER

DataVolume ::= INTEGER

DataVolumeIncoming ::= [APPLICATION 250] DataVolume

DataVolumeOutgoing ::= [APPLICATION 251] DataVolume

DateTime ::= SEQUENCE
{
  localTimeStamp LocalTimeStamp,
  utcTimeOffsetCode UtcTimeOffsetCode,
  ...
}

DateTimeLong ::= SEQUENCE
{
  localTimeStamp LocalTimeStamp,
  utcTimeOffset UtcTimeOffset,
  ...
}

DefaultCallHandlingIndicator ::= [APPLICATION 87] INTEGER

DepositTimeStamp ::= [APPLICATION 88] DateTime

Destination ::= [APPLICATION 89] SEQUENCE
{
  calledNumber CalledNumber OPTIONAL,
  dialledDigits DialledDigits OPTIONAL,
  calledPlace CalledPlace OPTIONAL,
  calledRegion CalledRegion OPTIONAL,
  sMSDestinationNumber SMSDestinationNumber OPTIONAL,
  ...
}

DestinationNetwork ::= [APPLICATION 90] NetworkId

DialledDigits ::= [APPLICATION 279] AsciiString

Discount ::= [APPLICATION 412] DiscountValue

DiscountableAmount ::= [APPLICATION 423] AbsoluteAmount

DiscountApplied ::= [APPLICATION 428] CHOICE
{
  fixedDiscountValue FixedDiscountValue,
  discountRate DiscountRate,
  ...
}

DiscountCode ::= [APPLICATION 91] INTEGER

DiscountInformation ::= [APPLICATION 96] SEQUENCE
{
  discountCode DiscountCode,
  discount Discount OPTIONAL,
  discountableAmount DiscountableAmount OPTIONAL,
  ...
}

Discounting ::= [APPLICATION 94] SEQUENCE
{
  discountCode DiscountCode,
  discountApplied DiscountApplied,
  ...
}

DiscountingList ::= [APPLICATION 95] SEQUENCE OF Discounting

DiscountRate ::= [APPLICATION 92] PercentageRate

DiscountValue ::= AbsoluteAmount

DistanceChargeBandCode ::= [APPLICATION 98] AsciiString (SIZE(1))

EarliestCallTimeStamp ::= [APPLICATION 101] DateTimeLong

ElementId ::= [APPLICATION 437] AsciiString

ElementType ::= [APPLICATION 438] INTEGER

EquipmentId ::= [APPLICATION 290] AsciiString

EquipmentIdType ::= [APPLICATION 322] INTEGER

Esn ::= [APPLICATION 103] NumberString

EventReference ::= [APPLICATION 435] AsciiString

ExchangeRate ::= [APPLICATION 104] INTEGER

ExchangeRateCode ::= [APPLICATION 105] Code

FileAvailableTimeStamp ::= [APPLICATION 107] DateTimeLong

FileCreationTimeStamp ::= [APPLICATION 108] DateTimeLong

FileSequenceNumber ::= [APPLICATION 109] NumberString (SIZE(5))

FileTypeIndicator ::= [APPLICATION 110] AsciiString (SIZE(1))

FixedDiscountValue ::= [APPLICATION 411] DiscountValue

Fnur ::= [APPLICATION 111] INTEGER

GeographicalLocation ::= [APPLICATION 113] SEQUENCE
{
  servingNetwork ServingNetwork OPTIONAL,
  servingBid ServingBid OPTIONAL,
  servingLocationDescription ServingLocationDescription OPTIONAL,
  ...
}

GprsBasicCallInformation ::= [APPLICATION 114] SEQUENCE
{
  gprsChargeableSubscriber GprsChargeableSubscriber,
  rapFileSequenceNumber RapFileSequenceNumber OPTIONAL,
  gprsDestination GprsDestination,
  callEventStartTimeStamp CallEventStartTimeStamp,
  totalCallEventDuration TotalCallEventDuration,
  causeForTerm CauseForTerm OPTIONAL,
  partialTypeIndicator PartialTypeIndicator OPTIONAL,
  pDPContextStartTimestamp PDPContextStartTimestamp OPTIONAL,
  networkInitPDPContext NetworkInitPDPContext OPTIONAL,
  chargingId ChargingId,
  ...
}

GprsChargeableSubscriber ::= [APPLICATION 115] SEQUENCE
{
  chargeableSubscriber ChargeableSubscriber OPTIONAL,
  pdpAddress PdpAddress OPTIONAL,
  networkAccessIdentifier NetworkAccessIdentifier OPTIONAL,
  ...
}

GprsDestination ::= [APPLICATION 116] SEQUENCE
{
  accessPointNameNI AccessPointNameNI,
  accessPointNameOI AccessPointNameOI OPTIONAL,
  ...
}

GprsLocationInformation ::= [APPLICATION 117] SEQUENCE
{
  gprsNetworkLocation GprsNetworkLocation,
  homeLocationInformation HomeLocationInformation OPTIONAL,
  geographicalLocation GeographicalLocation OPTIONAL,
  ...
}

GprsNetworkLocation ::= [APPLICATION 118] SEQUENCE
{
  recEntity RecEntityCodeList,
  locationArea LocationArea OPTIONAL,
  cellId CellId OPTIONAL,
  ...
}

GprsServiceUsed ::= [APPLICATION 121] SEQUENCE
{
  iMSSignallingContext IMSSignallingContext OPTIONAL,
  dataVolumeIncoming DataVolumeIncoming,
  dataVolumeOutgoing DataVolumeOutgoing,
  chargeInformationList ChargeInformationList,
  ...
}

GsmChargeableSubscriber ::= [APPLICATION 286] SEQUENCE
{
  imsi Imsi OPTIONAL,
  msisdn Msisdn OPTIONAL,
  ...
}

GuaranteedBitRate ::= [APPLICATION 420] OCTET STRING (SIZE(1))

HomeBid ::= [APPLICATION 122] Bid

HomeIdentifier ::= [APPLICATION 288] AsciiString

HomeIdType ::= [APPLICATION 311] INTEGER

HomeLocationDescription ::= [APPLICATION 413] LocationDescription

HomeLocationInformation ::= [APPLICATION 123] SEQUENCE
{
  homeBid HomeBid,
  homeLocationDescription HomeLocationDescription,
  ...
}

HorizontalAccuracyDelivered ::= [APPLICATION 392] INTEGER

HorizontalAccuracyRequested ::= [APPLICATION 385] INTEGER

HSCSDIndicator ::= [APPLICATION 424] AsciiString (SIZE(1))

Imei ::= [APPLICATION 128] BCDString (SIZE(7..8))

ImeiOrEsn ::= [APPLICATION 429] CHOICE
{
  imei Imei,
  esn Esn,
  ...
}

Imsi ::= [APPLICATION 129] BCDString (SIZE(3..8))

IMSSignallingContext ::= [APPLICATION 418] INTEGER

InternetServiceProvider ::= [APPLICATION 329] SEQUENCE
{
  ispIdType IspIdType,
  ispIdentifier IspIdentifier,
  ...
}

InternetServiceProviderIdList ::= [APPLICATION 330] SEQUENCE OF InternetServiceProvider

IspIdentifier ::= [APPLICATION 294] AsciiString

IspIdType ::= [APPLICATION 293] INTEGER

ISPList ::= [APPLICATION 378] SEQUENCE OF InternetServiceProvider

NetworkIdType ::= [APPLICATION 331] INTEGER

NetworkIdentifier ::= [APPLICATION 295] AsciiString

Network ::= [APPLICATION 332] SEQUENCE
{
  networkIdType NetworkIdType,
  networkIdentifier NetworkIdentifier,
  ...
}

NetworkList ::= [APPLICATION 333] SEQUENCE OF Network

LatestCallTimeStamp ::= [APPLICATION 133] DateTimeLong

LCSQosDelivered ::= [APPLICATION 390] SEQUENCE
{
  lCSTransactionStatus LCSTransactionStatus OPTIONAL,
  horizontalAccuracyDelivered HorizontalAccuracyDelivered OPTIONAL,
  verticalAccuracyDelivered VerticalAccuracyDelivered OPTIONAL,
  responseTime ResponseTime OPTIONAL,
  positioningMethod PositioningMethod OPTIONAL,
  trackingPeriod TrackingPeriod OPTIONAL,
  trackingFrequency TrackingFrequency OPTIONAL,
  ageOfLocation AgeOfLocation OPTIONAL,
  ...
}

LCSQosRequested ::= [APPLICATION 383] SEQUENCE
{
  lCSRequestTimestamp LCSRequestTimestamp,
  horizontalAccuracyRequested HorizontalAccuracyRequested OPTIONAL,
  verticalAccuracyRequested VerticalAccuracyRequested OPTIONAL,
  responseTimeCategory ResponseTimeCategory OPTIONAL,
  trackingPeriod TrackingPeriod OPTIONAL,
  trackingFrequency TrackingFrequency OPTIONAL,
  ...
}

LCSRequestTimestamp ::= [APPLICATION 384] DateTime

LCSSPIdentification ::= [APPLICATION 375] SEQUENCE
{
  contentProviderIdType ContentProviderIdType,
  contentProviderIdentifier ContentProviderIdentifier,
  ...
}

LCSSPIdentificationList ::= [APPLICATION 374] SEQUENCE OF LCSSPIdentification

LCSSPInformation ::= [APPLICATION 373] SEQUENCE
{
  lCSSPIdentificationList LCSSPIdentificationList,
  iSPList ISPList OPTIONAL,
  networkList NetworkList OPTIONAL,
  ...
}

LCSTransactionStatus ::= [APPLICATION 391] INTEGER

LocalCurrency ::= [APPLICATION 135] Currency

LocalTimeStamp ::= [APPLICATION 16] NumberString (SIZE(14))

LocationArea ::= [APPLICATION 136] INTEGER

LocationDescription ::= AsciiString

LocationIdentifier ::= [APPLICATION 289] AsciiString

LocationIdType ::= [APPLICATION 315] INTEGER

LocationInformation ::= [APPLICATION 138] SEQUENCE
{
  networkLocation NetworkLocation,
  homeLocationInformation HomeLocationInformation OPTIONAL,
  geographicalLocation GeographicalLocation OPTIONAL,
  ...
}

LocationServiceUsage ::= [APPLICATION 382] SEQUENCE
{
  lCSQosRequested LCSQosRequested,
  lCSQosDelivered LCSQosDelivered OPTIONAL,
  chargingTimeStamp ChargingTimeStamp OPTIONAL,
  chargeInformationList ChargeInformationList,
  ...
}

MaximumBitRate ::= [APPLICATION 421] OCTET STRING (SIZE(1))

Mdn ::= [APPLICATION 253] NumberString

MessageDescription ::= [APPLICATION 142] AsciiString

MessageDescriptionCode ::= [APPLICATION 141] Code

MessageDescriptionInformation ::= [APPLICATION 143] SEQUENCE
{
  messageDescriptionCode MessageDescriptionCode,
  messageDescription MessageDescription,
  ...
}

MessageStatus ::= [APPLICATION 144] INTEGER

MessageType ::= [APPLICATION 145] INTEGER

MessagingEventService ::= [APPLICATION 439] INTEGER

Min ::= [APPLICATION 146] NumberString (SIZE(2..15))

MinChargeableSubscriber ::= [APPLICATION 254] SEQUENCE
{
  min Min,
  mdn Mdn OPTIONAL,
  ...
}

MoBasicCallInformation ::= [APPLICATION 147] SEQUENCE
{
  chargeableSubscriber ChargeableSubscriber,
  rapFileSequenceNumber RapFileSequenceNumber OPTIONAL,
  destination Destination OPTIONAL,
  destinationNetwork DestinationNetwork OPTIONAL,
  callEventStartTimeStamp CallEventStartTimeStamp,
  totalCallEventDuration TotalCallEventDuration,
  simToolkitIndicator SimToolkitIndicator OPTIONAL,
  causeForTerm CauseForTerm OPTIONAL,
  ...
}

MobileSessionService ::= [APPLICATION 440] INTEGER

Msisdn ::= [APPLICATION 152] BCDString (SIZE(1..9))

MtBasicCallInformation ::= [APPLICATION 153] SEQUENCE
{
  chargeableSubscriber ChargeableSubscriber,
  rapFileSequenceNumber RapFileSequenceNumber OPTIONAL,
  callOriginator CallOriginator OPTIONAL,
  originatingNetwork OriginatingNetwork OPTIONAL,
  callEventStartTimeStamp CallEventStartTimeStamp,
  totalCallEventDuration TotalCallEventDuration,
  simToolkitIndicator SimToolkitIndicator OPTIONAL,
  causeForTerm CauseForTerm OPTIONAL,
  ...
}

NetworkAccessIdentifier ::= [APPLICATION 417] AsciiString

NetworkElement ::= [APPLICATION 441] SEQUENCE
{
  elementType ElementType,
  elementId ElementId,
  ...
}

NetworkElementList ::= [APPLICATION 442] SEQUENCE OF NetworkElement

NetworkId ::= AsciiString (SIZE(1..6))

NetworkInitPDPContext ::= [APPLICATION 245] INTEGER

NetworkLocation ::= [APPLICATION 156] SEQUENCE
{
  recEntityCode RecEntityCode,
  callReference CallReference OPTIONAL,
  locationArea LocationArea OPTIONAL,
  cellId CellId OPTIONAL,
  ...
}

NonChargedNumber ::= [APPLICATION 402] AsciiString

NonChargedParty ::= [APPLICATION 443] SEQUENCE
{
  nonChargedPartyNumber NonChargedPartyNumber OPTIONAL,
  nonChargedPublicUserId NonChargedPublicUserId OPTIONAL,
  ...
}

NonChargedPartyNumber ::= [APPLICATION 444] AddressStringDigits

NonChargedPublicUserId ::= [APPLICATION 445] AsciiString

NumberOfDecimalPlaces ::= [APPLICATION 159] INTEGER

ObjectType ::= [APPLICATION 281] INTEGER

OperatorSpecInfoList ::= [APPLICATION 162] SEQUENCE OF OperatorSpecInformation

OperatorSpecInformation ::= [APPLICATION 163] AsciiString

OrderPlacedTimeStamp ::= [APPLICATION 300] DateTime

OriginatingNetwork ::= [APPLICATION 164] NetworkId

PacketDataProtocolAddress ::= [APPLICATION 165] AsciiString

PaidIndicator ::= [APPLICATION 346] INTEGER

PartialTypeIndicator ::= [APPLICATION 166] AsciiString (SIZE(1))

PaymentMethod ::= [APPLICATION 347] INTEGER

PdpAddress ::= [APPLICATION 167] PacketDataProtocolAddress

PDPContextStartTimestamp ::= [APPLICATION 260] DateTime

PlmnId ::= [APPLICATION 169] AsciiString (SIZE(5))

PositioningMethod ::= [APPLICATION 395] INTEGER

PriorityCode ::= [APPLICATION 170] INTEGER

PublicUserId ::= [APPLICATION 446] AsciiString

RapFileSequenceNumber ::= [APPLICATION 181] FileSequenceNumber

RecEntityCode ::= [APPLICATION 184] Code

RecEntityCodeList ::= [APPLICATION 185] SEQUENCE OF RecEntityCode

RecEntityId ::= [APPLICATION 400] AsciiString

RecEntityInfoList ::= [APPLICATION 188] SEQUENCE OF RecEntityInformation

RecEntityInformation ::= [APPLICATION 183] SEQUENCE
{
  recEntityCode RecEntityCode,
  recEntityType RecEntityType,
  recEntityId RecEntityId,
  ...
}

RecEntityType ::= [APPLICATION 186] INTEGER

Recipient ::= [APPLICATION 182] PlmnId

ReleaseVersionNumber ::= [APPLICATION 189] INTEGER

RequestedDeliveryTimeStamp ::= [APPLICATION 301] DateTime

RequestedDestination ::= [APPLICATION 450] SEQUENCE
{
  requestedNumber RequestedNumber OPTIONAL,
  requestedPublicUserId RequestedPublicUserId OPTIONAL,
  ...
}

RequestedNumber ::= [APPLICATION 451] AddressStringDigits

RequestedPublicUserId ::= [APPLICATION 452] AsciiString

ResponseTime ::= [APPLICATION 394] INTEGER

ResponseTimeCategory ::= [APPLICATION 387] INTEGER

ScuBasicInformation ::= [APPLICATION 191] SEQUENCE
{
  chargeableSubscriber ScuChargeableSubscriber,
  chargedPartyStatus ChargedPartyStatus,
  nonChargedNumber NonChargedNumber,
  clirIndicator ClirIndicator OPTIONAL,
  originatingNetwork OriginatingNetwork OPTIONAL,
  destinationNetwork DestinationNetwork OPTIONAL,
  ...
}

ScuChargeType ::= [APPLICATION 192] SEQUENCE
{
  messageStatus MessageStatus,
  priorityCode PriorityCode,
  distanceChargeBandCode DistanceChargeBandCode OPTIONAL,
  messageType MessageType,
  messageDescriptionCode MessageDescriptionCode,
  ...
}

ScuTimeStamps ::= [APPLICATION 193] SEQUENCE
{
  depositTimeStamp DepositTimeStamp,
  completionTimeStamp CompletionTimeStamp,
  chargingPoint ChargingPoint,
  ...
}

ScuChargeableSubscriber ::= [APPLICATION 430] CHOICE
{
  gsmChargeableSubscriber GsmChargeableSubscriber,
  minChargeableSubscriber MinChargeableSubscriber,
  ...
}

Sender ::= [APPLICATION 196] PlmnId

ServiceStartTimestamp ::= [APPLICATION 447] DateTime

ServingBid ::= [APPLICATION 198] Bid

ServingLocationDescription ::= [APPLICATION 414] LocationDescription

ServingNetwork ::= [APPLICATION 195] AsciiString

ServingPartiesInformation ::= [APPLICATION 335] SEQUENCE
{
  contentProviderName ContentProviderName,
  contentProviderIdList ContentProviderIdList OPTIONAL,
  internetServiceProviderIdList InternetServiceProviderIdList OPTIONAL,
  networkList NetworkList OPTIONAL,
  ...
}

SessionChargeInfoList ::= [APPLICATION 448] SEQUENCE OF SessionChargeInformation

SessionChargeInformation ::= [APPLICATION 449] SEQUENCE
{
  chargedItem ChargedItem,
  exchangeRateCode ExchangeRateCode OPTIONAL,
  callTypeGroup CallTypeGroup,
  chargeDetailList ChargeDetailList,
  taxInformationList TaxInformationList OPTIONAL,
  ...
}

SimChargeableSubscriber ::= [APPLICATION 199] SEQUENCE
{
  imsi Imsi,
  msisdn Msisdn OPTIONAL,
  ...
}

SimToolkitIndicator ::= [APPLICATION 200] AsciiString (SIZE(1))

SMSDestinationNumber ::= [APPLICATION 419] AsciiString

SMSOriginator ::= [APPLICATION 425] AsciiString

SpecificationVersionNumber ::= [APPLICATION 201] INTEGER

SsParameters ::= [APPLICATION 204] AsciiString (SIZE(1..40))

SupplServiceActionCode ::= [APPLICATION 208] INTEGER

SupplServiceCode ::= [APPLICATION 209] HexString (SIZE(2))

SupplServiceUsed ::= [APPLICATION 206] SEQUENCE
{
  supplServiceCode SupplServiceCode,
  supplServiceActionCode SupplServiceActionCode,
  ssParameters SsParameters OPTIONAL,
  chargingTimeStamp ChargingTimeStamp,
  chargeInformation ChargeInformation OPTIONAL,
  basicServiceCodeList BasicServiceCodeList OPTIONAL,
  ...
}

TapCurrency ::= [APPLICATION 210] Currency

TapDecimalPlaces ::= [APPLICATION 244] INTEGER

TaxableAmount ::= [APPLICATION 398] AbsoluteAmount

Taxation ::= [APPLICATION 216] SEQUENCE
{
  taxCode TaxCode,
  taxType TaxType,
  taxRate TaxRate OPTIONAL,
  chargeType ChargeType OPTIONAL,
  taxIndicator TaxIndicator OPTIONAL,
  ...
}

TaxationList ::= [APPLICATION 211] SEQUENCE OF Taxation

TaxCode ::= [APPLICATION 212] INTEGER

TaxIndicator ::= [APPLICATION 432] AsciiString (SIZE(1))

TaxInformation ::= [APPLICATION 213] SEQUENCE
{
  taxCode TaxCode,
  taxValue TaxValue,
  taxableAmount TaxableAmount OPTIONAL,
  ...
}

TaxInformationList ::= [APPLICATION 214] SEQUENCE OF TaxInformation

TaxRate ::= [APPLICATION 215] NumberString (SIZE(7))

TaxType ::= [APPLICATION 217] AsciiString (SIZE(2))

TaxValue ::= [APPLICATION 397] AbsoluteAmount

TeleServiceCode ::= [APPLICATION 218] HexString (SIZE(2))

ThirdPartyInformation ::= [APPLICATION 219] SEQUENCE
{
  thirdPartyNumber ThirdPartyNumber OPTIONAL,
  clirIndicator ClirIndicator OPTIONAL,
  ...
}

ThirdPartyNumber ::= [APPLICATION 403] AddressStringDigits

ThreeGcamelDestination ::= [APPLICATION 431] CHOICE
{
  camelDestinationNumber CamelDestinationNumber,
  gprsDestination GprsDestination,
  ...
}

TotalAdvisedCharge ::= [APPLICATION 356] AbsoluteAmount

TotalAdvisedChargeRefund ::= [APPLICATION 357] AbsoluteAmount

TotalAdvisedChargeValue ::= [APPLICATION 360] SEQUENCE
{
  advisedChargeCurrency AdvisedChargeCurrency OPTIONAL,
  totalAdvisedCharge TotalAdvisedCharge,
  totalAdvisedChargeRefund TotalAdvisedChargeRefund OPTIONAL,
  totalCommission TotalCommission OPTIONAL,
  totalCommissionRefund TotalCommissionRefund OPTIONAL,
  ...
}

TotalAdvisedChargeValueList ::= [APPLICATION 361] SEQUENCE OF TotalAdvisedChargeValue

TotalCallEventDuration ::= [APPLICATION 223] INTEGER

TotalCharge ::= [APPLICATION 415] AbsoluteAmount

TotalChargeRefund ::= [APPLICATION 355] AbsoluteAmount

TotalCommission ::= [APPLICATION 358] AbsoluteAmount

TotalCommissionRefund ::= [APPLICATION 359] AbsoluteAmount

TotalDataVolume ::= [APPLICATION 343] DataVolume

TotalDiscountRefund ::= [APPLICATION 354] AbsoluteAmount

TotalDiscountValue ::= [APPLICATION 225] AbsoluteAmount

TotalTaxRefund ::= [APPLICATION 353] AbsoluteAmount

TotalTaxValue ::= [APPLICATION 226] AbsoluteAmount

TotalTransactionDuration ::= [APPLICATION 416] TotalCallEventDuration

TrackedCustomerEquipment ::= [APPLICATION 381] SEQUENCE
{
  equipmentIdType EquipmentIdType,
  equipmentId EquipmentId,
  ...
}

TrackedCustomerHomeId ::= [APPLICATION 377] SEQUENCE
{
  homeIdType HomeIdType,
  homeIdentifier HomeIdentifier,
  ...
}

TrackedCustomerHomeIdList ::= [APPLICATION 376] SEQUENCE OF TrackedCustomerHomeId

TrackedCustomerIdentification ::= [APPLICATION 372] SEQUENCE
{
  customerIdType CustomerIdType,
  customerIdentifier CustomerIdentifier,
  ...
}

TrackedCustomerIdList ::= [APPLICATION 370] SEQUENCE OF TrackedCustomerIdentification

TrackedCustomerInformation ::= [APPLICATION 367] SEQUENCE
{
  trackedCustomerIdList TrackedCustomerIdList,
  trackedCustomerHomeIdList TrackedCustomerHomeIdList OPTIONAL,
  trackedCustomerLocList TrackedCustomerLocList OPTIONAL,
  trackedCustomerEquipment TrackedCustomerEquipment OPTIONAL,
  ...
}

TrackedCustomerLocation ::= [APPLICATION 380] SEQUENCE
{
  locationIdType LocationIdType,
  locationIdentifier LocationIdentifier,
  ...
}

TrackedCustomerLocList ::= [APPLICATION 379] SEQUENCE OF TrackedCustomerLocation

TrackingCustomerEquipment ::= [APPLICATION 371] SEQUENCE
{
  equipmentIdType EquipmentIdType,
  equipmentId EquipmentId,
  ...
}

TrackingCustomerHomeId ::= [APPLICATION 366] SEQUENCE
{
  homeIdType HomeIdType,
  homeIdentifier HomeIdentifier,
  ...
}

TrackingCustomerHomeIdList ::= [APPLICATION 365] SEQUENCE OF TrackingCustomerHomeId

TrackingCustomerIdentification ::= [APPLICATION 362] SEQUENCE
{
  customerIdType CustomerIdType,
  customerIdentifier CustomerIdentifier,
  ...
}

TrackingCustomerIdList ::= [APPLICATION 299] SEQUENCE OF TrackingCustomerIdentification

TrackingCustomerInformation ::= [APPLICATION 298] SEQUENCE
{
  trackingCustomerIdList TrackingCustomerIdList,
  trackingCustomerHomeIdList TrackingCustomerHomeIdList OPTIONAL,
  trackingCustomerLocList TrackingCustomerLocList OPTIONAL,
  trackingCustomerEquipment TrackingCustomerEquipment OPTIONAL,
  ...
}

TrackingCustomerLocation ::= [APPLICATION 369] SEQUENCE
{
  locationIdType LocationIdType,
  locationIdentifier LocationIdentifier,
  ...
}

TrackingCustomerLocList ::= [APPLICATION 368] SEQUENCE OF TrackingCustomerLocation

TrackingFrequency ::= [APPLICATION 389] INTEGER

TrackingPeriod ::= [APPLICATION 388] INTEGER

TransactionAuthCode ::= [APPLICATION 342] AsciiString

TransactionDescriptionSupp ::= [APPLICATION 338] INTEGER

TransactionDetailDescription ::= [APPLICATION 339] AsciiString

TransactionIdentifier ::= [APPLICATION 341] AsciiString

TransactionShortDescription ::= [APPLICATION 340] AsciiString

TransactionStatus ::= [APPLICATION 303] INTEGER

TransferCutOffTimeStamp ::= [APPLICATION 227] DateTimeLong

TransparencyIndicator ::= [APPLICATION 228] INTEGER

UserProtocolIndicator ::= [APPLICATION 280] INTEGER

UtcTimeOffset ::= [APPLICATION 231] AsciiString (SIZE(5))

UtcTimeOffsetCode ::= [APPLICATION 232] Code

UtcTimeOffsetInfo ::= [APPLICATION 233] SEQUENCE
{
  utcTimeOffsetCode UtcTimeOffsetCode,
  utcTimeOffset UtcTimeOffset,
  ...
}

UtcTimeOffsetInfoList ::= [APPLICATION 234] SEQUENCE OF UtcTimeOffsetInfo

VerticalAccuracyDelivered ::= [APPLICATION 393] INTEGER

VerticalAccuracyRequested ::= [APPLICATION 386] INTEGER

AbsoluteAmount ::= INTEGER

Bid ::= AsciiString (SIZE(5))

Code ::= INTEGER

AsciiString ::= OCTET STRING

BCDString ::= OCTET STRING

Currency ::= OCTET STRING

HexString ::= OCTET STRING

NumberString ::= OCTET STRING

PercentageRate ::= INTEGER
