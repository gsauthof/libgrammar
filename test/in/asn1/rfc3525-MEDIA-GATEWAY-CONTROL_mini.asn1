MegacoMessage ::= SEQUENCE
{
  authHeader AuthenticationHeader OPTIONAL,
  mess Message
}

AuthenticationHeader ::= SEQUENCE
{
  secParmIndex SecurityParmIndex,
  seqNum SequenceNum,
  ad AuthData
}

SecurityParmIndex ::= OCTET STRING

SequenceNum ::= OCTET STRING

AuthData ::= OCTET STRING

Message ::= SEQUENCE
{
  version INTEGER,
  mId MId,
  messageBody MessageBody,
  ...
}

MessageBody ::= CHOICE
{
  messageError ErrorDescriptor,
  transactions Transactions
}

Transactions ::= SEQUENCE OF Transaction

MId ::= CHOICE
{
  ip4Address IP4Address,
  ip6Address IP6Address,
  domainName DomainName,
  deviceName PathName,
  mtpAddress OCTET STRING SIZE(2..4),
  ...
}

DomainName ::= SEQUENCE
{
  name IA5String,
  portNumber INTEGER OPTIONAL
}

IP4Address ::= SEQUENCE
{
  address OCTET STRING SIZE(4),
  portNumber INTEGER OPTIONAL
}

IP6Address ::= SEQUENCE
{
  address OCTET STRING SIZE(16),
  portNumber INTEGER OPTIONAL
}

PathName ::= IA5String

Transaction ::= CHOICE
{
  transactionRequest TransactionRequest,
  transactionPending TransactionPending,
  transactionReply TransactionReply,
  transactionResponseAck TransactionResponseAck,
  ...
}

TransactionId ::= INTEGER

TransactionRequest ::= SEQUENCE
{
  transactionId TransactionId,
  actions Actions,
  ...
}

Actions ::= SEQUENCE OF ActionRequest

TransactionPending ::= SEQUENCE
{
  transactionId TransactionId,
  ...
}

TransactionReply ::= SEQUENCE
{
  transactionId TransactionId,
  immAckRequired NULL OPTIONAL,
  transactionResult TransactionResult,
  ...
}

TransactionResult ::= CHOICE
{
  transactionError ErrorDescriptor,
  actionReplies ActionReplies
}

ActionReplies ::= SEQUENCE OF ActionReply

TransactionResponseAck ::= SEQUENCE OF TransactionAck

TransactionAck ::= SEQUENCE
{
  firstAck TransactionId,
  lastAck TransactionId OPTIONAL
}

ErrorDescriptor ::= SEQUENCE
{
  errorCode ErrorCode,
  errorText ErrorText OPTIONAL
}

ErrorCode ::= INTEGER

ErrorText ::= IA5String

ContextID ::= INTEGER

ActionRequest ::= SEQUENCE
{
  contextId ContextID,
  contextRequest ContextRequest OPTIONAL,
  contextAttrAuditReq ContextAttrAuditRequest OPTIONAL,
  commandRequests CommandRequests
}

CommandRequests ::= SEQUENCE OF CommandRequest

ActionReply ::= SEQUENCE
{
  contextId ContextID,
  errorDescriptor ErrorDescriptor OPTIONAL,
  contextReply ContextRequest OPTIONAL,
  commandReply CommandReplies
}

CommandReplies ::= SEQUENCE OF CommandReply

ContextRequest ::= SEQUENCE
{
  priority INTEGER OPTIONAL,
  emergency BOOLEAN OPTIONAL,
  topologyReq TopologyReq OPTIONAL,
  ...
}

TopologyReq ::= SEQUENCE OF TopologyRequest

ContextAttrAuditRequest ::= SEQUENCE
{
  topology NULL OPTIONAL,
  emergency NULL OPTIONAL,
  priority NULL OPTIONAL,
  ...
}

CommandRequest ::= SEQUENCE
{
  command Command,
  optional NULL OPTIONAL,
  wildcardReturn NULL OPTIONAL,
  ...
}

Command ::= CHOICE
{
  addReq AmmRequest,
  moveReq AmmRequest,
  modReq AmmRequest,
  subtractReq SubtractRequest,
  auditCapRequest AuditRequest,
  auditValueRequest AuditRequest,
  notifyReq NotifyRequest,
  serviceChangeReq ServiceChangeRequest,
  ...
}

CommandReply ::= CHOICE
{
  addReply AmmsReply,
  moveReply AmmsReply,
  modReply AmmsReply,
  subtractReply AmmsReply,
  auditCapReply AuditReply,
  auditValueReply AuditReply,
  notifyReply NotifyReply,
  serviceChangeReply ServiceChangeReply,
  ...
}

TopologyRequest ::= SEQUENCE
{
  terminationFrom TerminationID,
  terminationTo TerminationID,
  topologyDirection INTEGER,
  ...
}

AmmRequest ::= SEQUENCE
{
  terminationID TerminationIDList,
  descriptors Descriptors,
  ...
}

Descriptors ::= SEQUENCE OF AmmDescriptor

AmmDescriptor ::= CHOICE
{
  mediaDescriptor MediaDescriptor,
  modemDescriptor ModemDescriptor,
  muxDescriptor MuxDescriptor,
  eventsDescriptor EventsDescriptor,
  eventBufferDescriptor EventBufferDescriptor,
  signalsDescriptor SignalsDescriptor,
  digitMapDescriptor DigitMapDescriptor,
  auditDescriptor AuditDescriptor,
  ...
}

AmmsReply ::= SEQUENCE
{
  terminationID TerminationIDList,
  terminationAudit TerminationAudit OPTIONAL,
  ...
}

SubtractRequest ::= SEQUENCE
{
  terminationID TerminationIDList,
  auditDescriptor AuditDescriptor OPTIONAL,
  ...
}

AuditRequest ::= SEQUENCE
{
  terminationID TerminationID,
  auditDescriptor AuditDescriptor,
  ...
}

AuditReply ::= CHOICE
{
  contextAuditResult TerminationIDList,
  error ErrorDescriptor,
  auditResult AuditResult,
  ...
}

AuditResult ::= SEQUENCE
{
  terminationID TerminationID,
  terminationAuditResult TerminationAudit
}

TerminationAudit ::= SEQUENCE OF AuditReturnParameter

AuditReturnParameter ::= CHOICE
{
  errorDescriptor ErrorDescriptor,
  mediaDescriptor MediaDescriptor,
  modemDescriptor ModemDescriptor,
  muxDescriptor MuxDescriptor,
  eventsDescriptor EventsDescriptor,
  eventBufferDescriptor EventBufferDescriptor,
  signalsDescriptor SignalsDescriptor,
  digitMapDescriptor DigitMapDescriptor,
  observedEventsDescriptor ObservedEventsDescriptor,
  statisticsDescriptor StatisticsDescriptor,
  packagesDescriptor PackagesDescriptor,
  emptyDescriptors AuditDescriptor,
  ...
}

AuditDescriptor ::= SEQUENCE
{
  auditToken BIT STRING OPTIONAL,
  ...
}

NotifyRequest ::= SEQUENCE
{
  terminationID TerminationIDList,
  observedEventsDescriptor ObservedEventsDescriptor,
  errorDescriptor ErrorDescriptor OPTIONAL,
  ...
}

NotifyReply ::= SEQUENCE
{
  terminationID TerminationIDList,
  errorDescriptor ErrorDescriptor OPTIONAL,
  ...
}

ObservedEventsDescriptor ::= SEQUENCE
{
  requestId RequestID,
  observedEventLst ObservedEventLst
}

ObservedEventLst ::= SEQUENCE OF ObservedEvent

ObservedEvent ::= SEQUENCE
{
  eventName EventName,
  streamID StreamID OPTIONAL,
  eventParList EventParList,
  timeNotation TimeNotation OPTIONAL,
  ...
}

EventParList ::= SEQUENCE OF EventParameter

EventName ::= PkgdName

EventParameter ::= SEQUENCE
{
  eventParameterName Name,
  value Value,
  extraInfo ExtraInfo OPTIONAL,
  ...
}

ExtraInfo ::= CHOICE
{
  relation Relation,
  range BOOLEAN,
  sublist BOOLEAN
}

ServiceChangeRequest ::= SEQUENCE
{
  terminationID TerminationIDList,
  serviceChangeParms ServiceChangeParm,
  ...
}

ServiceChangeReply ::= SEQUENCE
{
  terminationID TerminationIDList,
  serviceChangeResult ServiceChangeResult,
  ...
}

ServiceChangeResult ::= CHOICE
{
  errorDescriptor ErrorDescriptor,
  serviceChangeResParms ServiceChangeResParm
}

WildcardField ::= OCTET STRING

TerminationID ::= SEQUENCE
{
  wildcard Wildcard,
  id OCTET STRING SIZE(1..8),
  ...
}

Wildcard ::= SEQUENCE OF WildcardField

TerminationIDList ::= SEQUENCE OF TerminationID

MediaDescriptor ::= SEQUENCE
{
  termStateDescr TerminationStateDescriptor OPTIONAL,
  streams Streams OPTIONAL,
  ...
}

Streams ::= CHOICE
{
  oneStream StreamParms,
  multiStream MultiStream
}

MultiStream ::= SEQUENCE OF StreamDescriptor

StreamDescriptor ::= SEQUENCE
{
  streamID StreamID,
  streamParms StreamParms
}

StreamParms ::= SEQUENCE
{
  localControlDescriptor LocalControlDescriptor OPTIONAL,
  localDescriptor LocalRemoteDescriptor OPTIONAL,
  remoteDescriptor LocalRemoteDescriptor OPTIONAL,
  ...
}

LocalControlDescriptor ::= SEQUENCE
{
  streamMode StreamMode OPTIONAL,
  reserveValue BOOLEAN OPTIONAL,
  reserveGroup BOOLEAN OPTIONAL,
  propertyParms PropertyParms,
  ...
}

PropertyParms ::= SEQUENCE OF PropertyParm

StreamMode ::= INTEGER

PropertyParm ::= SEQUENCE
{
  name PkgdName,
  value PPValue,
  extraInfo PPExtraInfo OPTIONAL,
  ...
}

PPValue ::= SEQUENCE OF OCTET STRING

PPExtraInfo ::= CHOICE
{
  relation Relation,
  range BOOLEAN,
  sublist BOOLEAN
}

Name ::= OCTET STRING

PkgdName ::= OCTET STRING

Relation ::= INTEGER

LocalRemoteDescriptor ::= SEQUENCE
{
  propGrps PropGrps,
  ...
}

PropGrps ::= SEQUENCE OF PropertyGroup

PropertyGroup ::= SEQUENCE OF PropertyParm

TerminationStateDescriptor ::= SEQUENCE
{
  propertyParms TSDPropertyParms,
  eventBufferControl EventBufferControl OPTIONAL,
  serviceState ServiceState OPTIONAL,
  ...
}

TSDPropertyParms ::= SEQUENCE OF PropertyParm

EventBufferControl ::= INTEGER

ServiceState ::= INTEGER

MuxDescriptor ::= SEQUENCE
{
  muxType MuxType,
  termList TermList,
  nonStandardData NonStandardData OPTIONAL,
  ...
}

TermList ::= SEQUENCE OF TerminationID

MuxType ::= INTEGER

StreamID ::= INTEGER

EventsDescriptor ::= SEQUENCE
{
  requestID RequestID OPTIONAL,
  eventList EventList,
  ...
}

EventList ::= SEQUENCE OF RequestedEvent

RequestedEvent ::= SEQUENCE
{
  pkgdName PkgdName,
  streamID StreamID OPTIONAL,
  eventAction RequestedActions OPTIONAL,
  evParList EvParList,
  ...
}

EvParList ::= SEQUENCE OF EventParameter

RequestedActions ::= SEQUENCE
{
  keepActive BOOLEAN OPTIONAL,
  eventDM EventDM OPTIONAL,
  secondEvent SecondEventsDescriptor OPTIONAL,
  signalsDescriptor SignalsDescriptor OPTIONAL,
  ...
}

EventDM ::= CHOICE
{
  digitMapName DigitMapName,
  digitMapValue DigitMapValue
}

SecondEventsDescriptor ::= SEQUENCE
{
  requestID RequestID OPTIONAL,
  eventList SEDEventList,
  ...
}

SEDEventList ::= SEQUENCE OF SecondRequestedEvent

SecondRequestedEvent ::= SEQUENCE
{
  pkgdName PkgdName,
  streamID StreamID OPTIONAL,
  eventAction SecondRequestedActions OPTIONAL,
  evParList SREEvParList,
  ...
}

SREEvParList ::= SEQUENCE OF EventParameter

SecondRequestedActions ::= SEQUENCE
{
  keepActive BOOLEAN OPTIONAL,
  eventDM EventDM OPTIONAL,
  signalsDescriptor SignalsDescriptor OPTIONAL,
  ...
}

EventBufferDescriptor ::= SEQUENCE OF EventSpec

EventSpec ::= SEQUENCE
{
  eventName EventName,
  streamID StreamID OPTIONAL,
  eventParList ESEventParList,
  ...
}

ESEventParList ::= SEQUENCE OF EventParameter

SignalsDescriptor ::= SEQUENCE OF SignalRequest

SignalRequest ::= CHOICE
{
  signal Signal,
  seqSigList SeqSigList,
  ...
}

SeqSigList ::= SEQUENCE
{
  id INTEGER,
  signalList SignalList
}

SignalList ::= SEQUENCE OF Signal

Signal ::= SEQUENCE
{
  signalName SignalName,
  streamID StreamID OPTIONAL,
  sigType SignalType OPTIONAL,
  duration INTEGER OPTIONAL,
  notifyCompletion NotifyCompletion OPTIONAL,
  keepActive BOOLEAN OPTIONAL,
  sigParList SigParList,
  ...
}

SigParList ::= SEQUENCE OF SigParameter

SignalType ::= INTEGER

SignalName ::= PkgdName

NotifyCompletion ::= BIT STRING

SigParameter ::= SEQUENCE
{
  sigParameterName Name,
  value Value,
  extraInfo SPExtraInfo OPTIONAL,
  ...
}

SPExtraInfo ::= CHOICE
{
  relation Relation,
  range BOOLEAN,
  sublist BOOLEAN
}

RequestID ::= INTEGER

ModemDescriptor ::= SEQUENCE
{
  mtl MTL,
  mpl MPL,
  nonStandardData NonStandardData OPTIONAL
}

MTL ::= SEQUENCE OF ModemType

MPL ::= SEQUENCE OF PropertyParm

ModemType ::= INTEGER

DigitMapDescriptor ::= SEQUENCE
{
  digitMapName DigitMapName OPTIONAL,
  digitMapValue DigitMapValue OPTIONAL
}

DigitMapName ::= Name

DigitMapValue ::= SEQUENCE
{
  startTimer INTEGER OPTIONAL,
  shortTimer INTEGER OPTIONAL,
  longTimer INTEGER OPTIONAL,
  digitMapBody IA5String,
  ...
}

ServiceChangeParm ::= SEQUENCE
{
  serviceChangeMethod ServiceChangeMethod,
  serviceChangeAddress ServiceChangeAddress OPTIONAL,
  serviceChangeVersion INTEGER OPTIONAL,
  serviceChangeProfile ServiceChangeProfile OPTIONAL,
  serviceChangeReason Value,
  serviceChangeDelay INTEGER OPTIONAL,
  serviceChangeMgcId MId OPTIONAL,
  timeStamp TimeNotation OPTIONAL,
  nonStandardData NonStandardData OPTIONAL,
  ...
}

ServiceChangeAddress ::= CHOICE
{
  portNumber INTEGER,
  ip4Address IP4Address,
  ip6Address IP6Address,
  domainName DomainName,
  deviceName PathName,
  mtpAddress OCTET STRING SIZE(2..4),
  ...
}

ServiceChangeResParm ::= SEQUENCE
{
  serviceChangeMgcId MId OPTIONAL,
  serviceChangeAddress ServiceChangeAddress OPTIONAL,
  serviceChangeVersion INTEGER OPTIONAL,
  serviceChangeProfile ServiceChangeProfile OPTIONAL,
  timestamp TimeNotation OPTIONAL,
  ...
}

ServiceChangeMethod ::= INTEGER

ServiceChangeProfile ::= SEQUENCE
{
  profileName IA5String SIZE(1..67)
}

PackagesDescriptor ::= SEQUENCE OF PackagesItem

PackagesItem ::= SEQUENCE
{
  packageName Name,
  packageVersion INTEGER,
  ...
}

StatisticsDescriptor ::= SEQUENCE OF StatisticsParameter

StatisticsParameter ::= SEQUENCE
{
  statName PkgdName,
  statValue Value OPTIONAL
}

NonStandardData ::= SEQUENCE
{
  nonStandardIdentifier NonStandardIdentifier,
  data OCTET STRING
}

NonStandardIdentifier ::= CHOICE
{
  object OBJECT IDENTIFIER,
  h221NonStandard H221NonStandard,
  experimental IA5String SIZE(8),
  ...
}

H221NonStandard ::= SEQUENCE
{
  t35CountryCode1 INTEGER,
  t35CountryCode2 INTEGER,
  t35Extension INTEGER,
  manufacturerCode INTEGER,
  ...
}

TimeNotation ::= SEQUENCE
{
  date IA5String SIZE(8),
  time IA5String SIZE(8)
}

Value ::= SEQUENCE OF OCTET STRING
